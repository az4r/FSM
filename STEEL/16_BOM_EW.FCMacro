import FreeCAD as App
import os, re
from PySide2 import QtWidgets

doc = App.ActiveDocument
if not doc or not doc.FileName:
    raise RuntimeError("Zapisz dokument przed uruchomieniem makra.")

DOC_DIR    = os.path.dirname(doc.FileName)
MAIN_DIR   = os.path.join(DOC_DIR, "MAIN")
SINGLE_DIR = os.path.join(DOC_DIR, "SINGLE")

re_ew     = re.compile(r"^(\d{3})_")   # element wysyłkowy
re_single = re.compile(r"^(\d{4})_")   # element pojedynczy

# --- Funkcje pomocnicze ---

def get_prefix(label):
    m = re_ew.match(label or "")
    return m.group(1) if m else None

def get_single_file_from_label(label):
    m = re_single.match(label or "")
    if not m:
        return None
    pref4 = m.group(1)
    return os.path.join(SINGLE_DIR, f"{pref4}.FCStd")

def get_profile_name(single_fcstd):
    if not single_fcstd or not os.path.isfile(single_fcstd):
        return "?"
    try:
        td = App.openDocument(single_fcstd)
    except Exception:
        return "?"
    try:
        for o in td.Objects:
            lbl = o.Label or ""
            if "frame" in lbl.lower() or o.Name.lower().startswith("frame"):
                if hasattr(o, "Profile") and o.Profile:
                    prof_obj = o.Profile
                    if hasattr(prof_obj, "Label") and prof_obj.Label:
                        return prof_obj.Label
                for c in getattr(o, "OutList", []):
                    if hasattr(c, "Label") and c.Label:
                        return c.Label
                return o.Label or "?"
        for o in td.Objects:
            if hasattr(o, "Shape") and o.Shape and not o.Shape.isNull():
                return o.Label or "?"
        return "?"
    finally:
        try:
            App.closeDocument(td.Name)
        except Exception:
            pass

def get_dims_from_bbox(obj):
    if not hasattr(obj,"Shape") or not obj.Shape or obj.Shape.isNull():
        return (0.0,0.0,0.0)
    bb = obj.Shape.BoundBox
    dims = [bb.XLength, bb.YLength, bb.ZLength]
    dims.sort(reverse=True)
    return dims[0], dims[1], dims[2]

# --- Dialogi PySide2 z informacją o aktualnym elemencie ---

apply_to_all_mat = False
global_material = "S355J2"

apply_to_all_dens = False
global_density = 7850.0  # kg/m³

def ask_material(element_label, default="S355J2"):
    global apply_to_all_mat, global_material
    if apply_to_all_mat:
        return global_material
    dialog = QtWidgets.QDialog()
    dialog.setWindowTitle("Gatunek stali")
    layout = QtWidgets.QVBoxLayout(dialog)

    lbl_elem = QtWidgets.QLabel(f"Element: {element_label}")
    lbl_elem.setStyleSheet("font-weight: bold;")
    layout.addWidget(lbl_elem)

    form_layout = QtWidgets.QHBoxLayout()
    label = QtWidgets.QLabel("Gatunek stali:")
    textbox = QtWidgets.QLineEdit()
    textbox.setText(default)
    form_layout.addWidget(label)
    form_layout.addWidget(textbox)
    layout.addLayout(form_layout)

    checkbox = QtWidgets.QCheckBox("Zastosuj do wszystkich pozycji")
    layout.addWidget(checkbox)

    button_box = QtWidgets.QDialogButtonBox(QtWidgets.QDialogButtonBox.Ok)
    layout.addWidget(button_box)
    button_box.accepted.connect(dialog.accept)

    if dialog.exec_() == QtWidgets.QDialog.Accepted:
        mat = textbox.text().strip() or default
        if checkbox.isChecked():
            apply_to_all_mat = True
            global_material = mat
        return mat
    return default

def ask_density(element_label, default=7850.0):
    global apply_to_all_dens, global_density
    if apply_to_all_dens:
        return global_density
    dialog = QtWidgets.QDialog()
    dialog.setWindowTitle("Gęstość stali")
    layout = QtWidgets.QVBoxLayout(dialog)

    lbl_elem = QtWidgets.QLabel(f"Element: {element_label}")
    lbl_elem.setStyleSheet("font-weight: bold;")
    layout.addWidget(lbl_elem)

    form_layout = QtWidgets.QHBoxLayout()
    label = QtWidgets.QLabel("Gęstość stali:")
    textbox = QtWidgets.QLineEdit()
    textbox.setText(str(default))
    unit = QtWidgets.QLabel("kg/m³")
    form_layout.addWidget(label)
    form_layout.addWidget(textbox)
    form_layout.addWidget(unit)
    layout.addLayout(form_layout)

    checkbox = QtWidgets.QCheckBox("Zastosuj do wszystkich pozycji")
    layout.addWidget(checkbox)

    button_box = QtWidgets.QDialogButtonBox(QtWidgets.QDialogButtonBox.Ok)
    layout.addWidget(button_box)
    button_box.accepted.connect(dialog.accept)

    if dialog.exec_() == QtWidgets.QDialog.Accepted:
        try:
            dens = float(textbox.text().strip())
        except Exception:
            dens = default
        if checkbox.isChecked():
            apply_to_all_dens = True
            global_density = dens
        return dens
    return default

# --- Zbieranie danych ---

ew_data = {}
for o in doc.Objects:
    pref = get_prefix(o.Label or "")
    if not pref:
        continue
    ew = ew_data.setdefault(pref, {"ilosc":0, "dlugosc":0.0, "nazwa":"?", "szer":0.0, "wys":0.0})
    ew["ilosc"] += 1

for pref, data in ew_data.items():
    fcstd_path = os.path.join(MAIN_DIR, f"{pref}.FCStd")
    if not os.path.isfile(fcstd_path):
        continue
    try:
        td = App.openDocument(fcstd_path)
    except Exception:
        continue
    try:
        parts = [o for o in td.Objects if re_single.match(o.Label or "")]
        total_len = 0.0
        szer = 0.0
        wys = 0.0
        profile_name = data["nazwa"]
        for p in parts:
            L, W, H = get_dims_from_bbox(p)
            total_len += L
            szer = max(szer, W)
            wys = max(wys, H)
            sf = get_single_file_from_label(p.Label)
            if (profile_name == "?" or not profile_name) and sf:
                profile_name = get_profile_name(sf)
        data["dlugosc"] = total_len
        data["szer"] = szer
        data["wys"] = wys
        data["nazwa"] = profile_name or "?"
    finally:
        try:
            App.closeDocument(td.Name)
        except Exception:
            pass

# --- Arkusz ---

if "BOM_EW" in doc.Objects:
    sheet = doc.getObject("BOM_EW")
    try:
        sheet.clearAll()
    except Exception:
        # fallback: overwrite region if clearAll not reliable
        max_rows = 500
        cols = ['A','B','C','D','E','F','G','H','I']
        for r in range(1, max_rows+1):
            for c in cols:
                try:
                    sheet.set(f"{c}{r}", "")
                except Exception:
                    pass
else:
    sheet = doc.addObject("Spreadsheet::Sheet","BOM_EW")

# Nagłówek (bez scalania)
try:
    sheet.set("A1", "LIST OF MAIN ELEMENTS")
except Exception:
    pass

# Nagłówki kolumn (od wiersza 2)
sheet.set("A2", "ITEM")
sheet.set("B2", "NAME")
sheet.set("C2", "QUANTITY (pcs.)")
sheet.set("D2", "LENGHT [mm]")
sheet.set("E2", "WIDTH [mm]")
sheet.set("F2", "HEIGHT [mm]")
sheet.set("G2", "MATERIAL")
sheet.set("H2", "WEIGHT OF 1 pcs. [kg]")
sheet.set("I2", "WEIGHT [kg]")

row = 3
total_weight = 0.0

for pref, data in sorted(ew_data.items()):
    # pytamy o materiał i gęstość z widocznym numerem elementu
    material = ask_material(pref)
    density = ask_density(pref)

    # objętość w m3
    vol_m3 = (data["dlugosc"] * data["szer"] * data["wys"]) / 1e9
    waga_elem = vol_m3 * density
    waga_total = waga_elem * data["ilosc"]

    sheet.set(f"A{row}", pref)
    sheet.set(f"B{row}", data["nazwa"])
    sheet.set(f"C{row}", str(data["ilosc"]))
    sheet.set(f"D{row}", f"{data['dlugosc']:.2f}")
    sheet.set(f"E{row}", f"{data['szer']:.2f}")
    sheet.set(f"F{row}", f"{data['wys']:.2f}")
    sheet.set(f"G{row}", material)
    sheet.set(f"H{row}", f"{waga_elem:.3f}")
    sheet.set(f"I{row}", f"{waga_total:.3f}")

    total_weight += waga_total
    row += 1

# Podsumowanie pod tabelą
sheet.set(f"H{row}", "TOTAL WEIGHT [kg]")
sheet.set(f"I{row}", f"{total_weight:.3f}")

try:
    doc.recompute()
except Exception:
    pass

App.Console.PrintMessage("Arkusz BOM_EW utworzony z nagłówkiem i podsumowaniem.\n")

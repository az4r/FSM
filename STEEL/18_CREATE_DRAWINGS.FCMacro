import FreeCAD as App, os, re, json
import a2p_importpart
import TechDraw
from PySide2 import QtWidgets

# --- Funkcje pomocnicze ---
def log(msg):
    App.Console.PrintMessage(str(msg) + "\n")

def get_project_dir():
    if App.ActiveDocument and App.ActiveDocument.FileName:
        return os.path.dirname(App.ActiveDocument.FileName)
    else:
        raise Exception("Brak aktywnego dokumentu z zapisaną ścieżką")

def list_templates():
    tpl_dir = os.path.join(App.getResourceDir(), "Mod", "TechDraw", "Templates")
    if not os.path.isdir(tpl_dir):
        log(f"!!! Nie znaleziono katalogu Templates: {tpl_dir}")
        return []
    return [f for f in os.listdir(tpl_dir) if f.lower().endswith(".svg")]

def select_template_and_scale():
    files = list_templates()
    if not files:
        return None, None
    dlg = QtWidgets.QDialog()
    dlg.setWindowTitle("Ustawienia rysunku TechDraw")
    layout = QtWidgets.QVBoxLayout(dlg)

    scale_layout = QtWidgets.QHBoxLayout()
    scale_label = QtWidgets.QLabel("Skala:")
    scale_combo = QtWidgets.QComboBox()
    scale_combo.addItems(["1:1", "1:10", "1:50", "1:100", "1:200"])
    scale_layout.addWidget(scale_label)
    scale_layout.addWidget(scale_combo)
    layout.addLayout(scale_layout)

    tpl_label = QtWidgets.QLabel("Szablon:")
    tpl_combo = QtWidgets.QComboBox()
    tpl_combo.addItems(files)
    layout.addWidget(tpl_label)
    layout.addWidget(tpl_combo)

    btn_ok = QtWidgets.QPushButton("OK")
    layout.addWidget(btn_ok)
    btn_ok.clicked.connect(dlg.accept)

    dlg.exec_()
    return tpl_combo.currentText(), scale_combo.currentText()

# --- Tworzenie złożeń (create_assembly) ---
def create_assembly(docname, src_dir, draw_dir):
    doc = App.newDocument(docname)
    App.setActiveDocument(doc.Name)
    App.ActiveDocument = doc
    doc_path = os.path.join(draw_dir, f"{docname}.FCStd")
    try:
        doc.saveAs(doc_path)
    except Exception:
        pass

    files = [f for f in os.listdir(src_dir) if f.lower().endswith(".fcstd")]
    if not files:
        log(f"!!! Brak plików w katalogu: {src_dir}")
        return doc

    offset = 0
    for f in files:
        filepath = os.path.join(src_dir, f)
        try:
            root = a2p_importpart.importPartFromFile(doc, filepath)
            if root:
                root.Placement.Base.x = offset
                log(f">>> Zaimportowano {f} na X={offset}")
                offset += 30000
        except Exception as e:
            log(f"!!! Błąd importu {f}: {e}")

    try:
        doc.recompute()
        doc.save()
    except Exception:
        pass
    log(f">>> Utworzono {docname} z {len(files)} plików")
    return doc

# --- Zbieranie danych EP (rejestrujemy właścicieli EW) ---
def get_dims_from_bbox(obj):
    if not hasattr(obj, "Shape") or not obj.Shape or obj.Shape.isNull():
        return (0.0, 0.0, 0.0)
    bb = obj.Shape.BoundBox
    dims = [bb.XLength, bb.YLength, bb.ZLength]
    dims.sort(reverse=True)
    return dims[0], dims[1], dims[2]

def collect_single_data(main_doc, single_dir, main_dir):
    re_ew     = re.compile(r"^(\d{3})_")
    re_single = re.compile(r"^(\d{4})_")
    single_data = {}

    # 1) EP w modelu centralnym (inicjalizacja)
    for o in main_doc.Objects:
        m = re_single.match(o.Label or "")
        if not m: continue
        pref = m.group(1)
        sd = single_data.setdefault(pref, {"ilosc":0,"dlugosc":0.0,"szer":0.0,"wys":0.0,"nazwa":"?","ews": set()})
        sd["ilosc"] += 1

    # 2) EP wewnątrz EW (z plików MAIN) -> rejestrujemy właścicieli EW
    for o in main_doc.Objects:
        m = re_ew.match(o.Label or "")
        if not m: continue
        pref_ew = m.group(1)
        fcstd_path = os.path.join(main_dir, f"{pref_ew}.FCStd")
        if not os.path.isfile(fcstd_path): continue
        try:
            td = App.openDocument(fcstd_path)
        except Exception:
            continue
        try:
            for p in td.Objects:
                m2 = re_single.match(p.Label or "")
                if not m2: continue
                pref_single = m2.group(1)
                sd = single_data.setdefault(pref_single, {"ilosc":0,"dlugosc":0.0,"szer":0.0,"wys":0.0,"nazwa":"?","ews": set()})
                sd["ilosc"] += 1
                sd["ews"].add(pref_ew)
        finally:
            try:
                App.closeDocument(td.Name)
            except Exception:
                pass

    # 3) Uzupełnienie danych z SINGLE (wymiary + nazwa)
    for pref, data in single_data.items():
        fcstd_path = os.path.join(single_dir, f"{pref}.FCStd")
        if not os.path.isfile(fcstd_path): continue
        try:
            td = App.openDocument(fcstd_path)
        except Exception:
            continue
        try:
            for o in td.Objects:
                if hasattr(o, "Shape") and o.Shape and not o.Shape.isNull():
                    L,W,H = get_dims_from_bbox(o)
                    data["dlugosc"] = max(data["dlugosc"], L)
                    data["szer"]    = max(data["szer"], W)
                    data["wys"]     = max(data["wys"], H)
                    if data["nazwa"] == "?":
                        if o.Label and o.Label.lower() != "line":
                            data["nazwa"] = o.Label
        finally:
            try:
                App.closeDocument(td.Name)
            except Exception:
                pass

    # Zamień set -> lista dla serializacji
    for k,v in single_data.items():
        if isinstance(v.get("ews"), set):
            v["ews"] = sorted(list(v["ews"]))

    return single_data

def export_single_data_to_file(single_data, tmp_file):
    with open(tmp_file, "w", encoding="utf-8") as f:
        json.dump(single_data, f, indent=2)
    log(f"[DEBUG] Zapisano dane EP do {tmp_file}")

# --- Import arkusza BOM per EW (filtr wg właścicieli ews) z fallbackiem i debugiem ---
def import_single_data_to_sheet_for_ew(doc, tmp_file, ew_label, main_dir=None, single_dir=None):
    if not os.path.isfile(tmp_file):
        log(f"[DEBUG] brak tmp_file: {tmp_file}")
        return None

    with open(tmp_file, "r", encoding="utf-8") as f:
        single_data = json.load(f)

    ew_prefix = (ew_label.split("_")[0]).strip()

    # wybierz EP które mają ew_prefix w polu 'ews'
    filtered = []
    for pref, data in single_data.items():
        owners = data.get("ews") or []
        if ew_prefix in owners:
            filtered.append(pref)

    log(f"[DEBUG] EW {ew_label} prefix={ew_prefix} -> total EP keys={len(single_data)}; matched={len(filtered)}; matched_list={sorted(filtered)}")

    # fallback: jeśli pusto, spróbuj wyciągnąć listę EP z pliku MAIN/<ew_prefix>.FCStd
    if not filtered and main_dir:
        main_fcstd = os.path.join(main_dir, f"{ew_prefix}.FCStd")
        if os.path.isfile(main_fcstd):
            try:
                td = App.openDocument(main_fcstd)
            except Exception as e:
                log(f"[DEBUG] Nie można otworzyć {main_fcstd}: {e}")
                td = None
            if td:
                try:
                    re_single = re.compile(r"^(\d{4})_")
                    found = []
                    for o in td.Objects:
                        m = re_single.match(o.Label or "")
                        if m:
                            found.append(m.group(1))
                    log(f"[DEBUG] Fallback: EP found inside MAIN/{ew_prefix}.FCStd: {found}")
                    filtered = [k for k in found if k in single_data]
                    log(f"[DEBUG] Fallback: filtered_keys present in tmp_file: {filtered}")
                finally:
                    try:
                        App.closeDocument(td.Name)
                    except Exception:
                        pass

    if not filtered:
        return None

    sheet_name = f"BOM_{ew_label}"
    if sheet_name in doc.Objects:
        sheet = doc.getObject(sheet_name)
        try:
            sheet.clearAll()
        except Exception:
            pass
    else:
        sheet = doc.addObject("Spreadsheet::Sheet", sheet_name)

    # Wypełnij arkusz
    sheet.set("A1", f"LISTA ELEMENTÓW POJEDYNCZYCH DLA EW {ew_prefix}")
    sheet.set("A2","Nr")
    sheet.set("B2","Nazwa")
    sheet.set("C2","Ilość")
    sheet.set("D2","Długość [mm]")
    sheet.set("E2","Szerokość [mm]")
    sheet.set("F2","Wysokość [mm]")

    row = 3
    for pref in sorted(filtered):
        data = single_data.get(pref, {})
        sheet.set(f"A{row}", pref)
        sheet.set(f"B{row}", data.get("nazwa","?"))
        sheet.set(f"C{row}", str(data.get("ilosc",0)))
        sheet.set(f"D{row}", f"{data.get('dlugosc',0.0):.2f}")
        sheet.set(f"E{row}", f"{data.get('szer',0.0):.2f}")
        sheet.set(f"F{row}", f"{data.get('wys',0.0):.2f}")
        row += 1

    try:
        doc.recompute()
    except Exception:
        pass
    log(f"[DEBUG] Utworzono sheet {sheet_name} z {len(filtered)} wpisami")
    return sheet

# --- Rysunki + ustawienie CellStart/CellEnd dla DrawViewSpreadsheet ---
def create_drawings_for_main(doc, template_name, scale_str, tmp_file, main_dir, single_dir):
    tpl_dir = os.path.join(App.getResourceDir(), "Mod", "TechDraw", "Templates")
    tpl_path = os.path.join(tpl_dir, template_name)
    if not os.path.isfile(tpl_path):
        log(f"!!! Nie znaleziono szablonu: {tpl_path}")
        return

    try:
        num, den = scale_str.split(":")
        scale_val = float(num) / float(den)
    except:
        scale_val = 1.0

    for obj in doc.Objects:
        if obj.TypeId in ("App::Part", "Part::FeaturePython"):
            try:
                template = doc.addObject('TechDraw::DrawSVGTemplate', f"Template_{obj.Label}")
                template.Template = tpl_path
                page = doc.addObject('TechDraw::DrawPage', f"Page_{obj.Label}")
                page.Template = template

                max_dim = 3000.0
                margin  = 30.0
                view_size = max_dim * scale_val
                offset_y = view_size/2 + margin
                offset_x = view_size + margin

                view_xy = doc.addObject('TechDraw::DrawViewPart', f"ViewXY_{obj.Label}")
                view_xy.Source = [obj]
                view_xy.Direction = (0,0,1)
                view_xy.ScaleType = "Custom"
                view_xy.Scale = scale_val
                page.addView(view_xy)
                view_xy.X = 0
                view_xy.Y = offset_y

                view_xz = doc.addObject('TechDraw::DrawViewPart', f"ViewXZ_{obj.Label}")
                view_xz.Source = [obj]
                view_xz.Direction = (0,1,0)
                view_xz.ScaleType = "Custom"
                view_xz.Scale = scale_val
                page.addView(view_xz)
                view_xz.X = 0
                view_xz.Y = -offset_y

                view_iso = doc.addObject('TechDraw::DrawViewPart', f"ViewISO_{obj.Label}")
                view_iso.Source = [obj]
                view_iso.Direction = (1,1,1)
                view_iso.ScaleType = "Custom"
                view_iso.Scale = scale_val
                page.addView(view_iso)
                view_iso.X = offset_x
                view_iso.Y = -offset_y

                pw = float(template.Width)
                ph = float(template.Height)
                page_center_x = pw / 2
                page_center_y = ph / 2
                min_x = min(float(view_xy.X), float(view_iso.X))
                max_x = max(float(view_xy.X), float(view_iso.X))
                center_group_x = (min_x + max_x) / 2
                dx = page_center_x - center_group_x
                dy = page_center_y
                for v in [view_xy, view_xz, view_iso]:
                    v.X = float(v.X) + dx
                    v.Y = float(v.Y) + dy

                # BOM per-EW: utwórz sheet tylko dla EP przypisanych do tego EW
                sheet = import_single_data_to_sheet_for_ew(doc, tmp_file, obj.Label, main_dir=main_dir, single_dir=single_dir)
                if sheet:
                    # policz ostatni użyty wiersz w arkuszu sheet (kolumna A)
                    last_row = 2
                    try:
                        r = 3
                        while True:
                            val = sheet.get(f"A{r}")
                            if val is None or str(val).strip() == "":
                                break
                            last_row = r
                            r += 1
                    except Exception:
                        pass

                    cell_start = "A1"
                    cell_end = f"F{last_row}"

                    try:
                        doc.recompute()
                    except Exception:
                        pass

                    table_view = doc.addObject("TechDraw::DrawViewSpreadsheet", f"Table_{obj.Label}")
                    table_view.Source = sheet

                    # ustaw zakres komórek dla widoku (CellStart, CellEnd) - próbujemy kilka opcji
                    try:
                        table_view.CellStart = cell_start
                        table_view.CellEnd = cell_end
                    except Exception:
                        try:
                            vo = table_view.ViewObject
                            if hasattr(vo, "CellStart"):
                                vo.CellStart = cell_start
                            if hasattr(vo, "CellEnd"):
                                vo.CellEnd = cell_end
                        except Exception:
                            pass

                    # spróbuj dopasować wygląd
                    try:
                        vo = table_view.ViewObject
                        if hasattr(vo, "FontSize"):
                            vo.FontSize = 10
                        if hasattr(vo, "RowHeight"):
                            vo.RowHeight = 6
                        vo.Visibility = True
                    except Exception:
                        pass

                    try:
                        table_view.Width = 160.0
                        table_view.Height = 90.0
                    except Exception:
                        pass

                    page.addView(table_view)

                    table_view.X = 30.0
                    table_view.Y = 30.0

                    try:
                        table_view.recompute()
                    except Exception:
                        pass
                    try:
                        doc.recompute()
                    except Exception:
                        pass

                    log(f"[DEBUG] Dodano tabelę BOM (sheet {sheet.Name}) dla {obj.Label} cell_range={cell_start}:{cell_end}")
                else:
                    log(f"[DEBUG] Brak danych EP dla {obj.Label}")

                log(f">>> Utworzono rysunek dla {obj.Label} w skali {scale_str}")

            except Exception as e:
                log(f"!!! Błąd przy tworzeniu rysunku dla {obj.Label}: {e}")

    try:
        doc.recompute()
        doc.save()
    except Exception:
        pass

# --- Główna logika ---
try:
    proj_dir   = get_project_dir()
    single_dir = os.path.join(proj_dir, "SINGLE")
    main_dir   = os.path.join(proj_dir, "MAIN")
    draw_dir   = os.path.join(proj_dir, "DRAWINGS")
    os.makedirs(draw_dir, exist_ok=True)

    log("=== START CREATE_DRAWINGS ===")

    # 1) Tworzymy złożenia
    create_assembly("SINGLE_ASSEMBLY", single_dir, draw_dir)
    main_doc = create_assembly("MAIN_ASSEMBLY", main_dir, draw_dir)

    # 2) Zbieramy EP i zapisujemy do pliku tymczasowego
    tmp_file = os.path.join(proj_dir, "bom_ep_tmp.json")
    single_data = collect_single_data(main_doc, single_dir, main_dir)
    export_single_data_to_file(single_data, tmp_file)

    # DEBUG: pokaż klucze
    try:
        with open(tmp_file, "r", encoding="utf-8") as _f:
            jd = json.load(_f)
        log(f"[DEBUG] tmp_file={tmp_file}")
        log(f"[DEBUG] total EP keys: {len(jd)} -> {sorted(jd.keys())[:200]}")
    except Exception as e:
        log(f"[DEBUG] Nie można odczytać tmp_file: {e}")

    # 3) Tworzymy rysunki z BOM per EW
    if main_doc:
        chosen_tpl, chosen_scale = select_template_and_scale()
        if chosen_tpl and chosen_scale:
            log(f"Wybrano szablon: {chosen_tpl}, skala: {chosen_scale}")
            create_drawings_for_main(main_doc, chosen_tpl, chosen_scale, tmp_file, main_dir, single_dir)
        else:
            log("!!! Nie wybrano szablonu lub skali – pomijam generowanie rysunków")

    # 4) Sprzątanie
    if os.path.isfile(tmp_file):
        try:
            os.remove(tmp_file)
            log(f"[DEBUG] Usunięto plik tymczasowy {tmp_file}")
        except Exception as e:
            log(f"[DEBUG] Nie udało się usunąć pliku tymczasowego: {e}")

    log("=== KONIEC CREATE_DRAWINGS ===")

except Exception as e:
    log(f"!!! FAIL: {e}")

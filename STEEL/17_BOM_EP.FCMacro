import FreeCAD as App
import os, re
from PySide2 import QtWidgets

doc = App.ActiveDocument
if not doc or not doc.FileName:
    raise RuntimeError("Zapisz dokument przed uruchomieniem makra.")

DOC_DIR    = os.path.dirname(doc.FileName)
MAIN_DIR   = os.path.join(DOC_DIR, "MAIN")
SINGLE_DIR = os.path.join(DOC_DIR, "SINGLE")

re_ew     = re.compile(r"^(\d{3})_")   # element wysyłkowy
re_single = re.compile(r"^(\d{4})_")   # element pojedynczy

# --- Funkcje pomocnicze ---

def get_profile_name(single_fcstd):
    if not single_fcstd or not os.path.isfile(single_fcstd):
        return "?"
    try:
        td = App.openDocument(single_fcstd)
    except Exception:
        return "?"
    try:
        for o in td.Objects:
            lbl = o.Label or ""
            if "frame" in lbl.lower() or o.Name.lower().startswith("frame"):
                if hasattr(o, "Profile") and o.Profile:
                    prof_obj = o.Profile
                    if hasattr(prof_obj, "Label") and prof_obj.Label:
                        return prof_obj.Label
                for c in getattr(o, "OutList", []):
                    if hasattr(c, "Label") and c.Label:
                        return c.Label
                return o.Label or "?"
        for o in td.Objects:
            if hasattr(o, "Shape") and o.Shape and not o.Shape.isNull():
                return o.Label or "?"
        return "?"
    finally:
        try:
            App.closeDocument(td.Name)
        except Exception:
            pass

def get_dims_from_bbox(obj):
    if not hasattr(obj,"Shape") or not obj.Shape or obj.Shape.isNull():
        return (0.0,0.0,0.0)
    bb = obj.Shape.BoundBox
    dims = [bb.XLength, bb.YLength, bb.ZLength]
    dims.sort(reverse=True)
    return dims[0], dims[1], dims[2]

# --- Dialogi PySide2 z informacją o aktualnym elemencie (tylko OK) ---

apply_to_all_mat = False
global_material = "S355J2"

apply_to_all_dens = False
global_density = 7850.0  # kg/m³

def ask_material(element_label, default="S355J2"):
    global apply_to_all_mat, global_material
    if apply_to_all_mat:
        return global_material
    dlg = QtWidgets.QDialog()
    dlg.setWindowTitle("Gatunek stali")
    layout = QtWidgets.QVBoxLayout(dlg)

    lbl_elem = QtWidgets.QLabel(f"Element: {element_label}")
    lbl_elem.setStyleSheet("font-weight: bold;")
    layout.addWidget(lbl_elem)

    form_layout = QtWidgets.QHBoxLayout()
    label = QtWidgets.QLabel("Gatunek stali:")
    textbox = QtWidgets.QLineEdit()
    textbox.setText(default)
    form_layout.addWidget(label)
    form_layout.addWidget(textbox)
    layout.addLayout(form_layout)

    checkbox = QtWidgets.QCheckBox("Zastosuj do wszystkich pozycji")
    layout.addWidget(checkbox)

    button_box = QtWidgets.QDialogButtonBox(QtWidgets.QDialogButtonBox.Ok)
    layout.addWidget(button_box)
    button_box.accepted.connect(dlg.accept)

    if dlg.exec_() == QtWidgets.QDialog.Accepted:
        mat = textbox.text().strip() or default
        if checkbox.isChecked():
            apply_to_all_mat = True
            global_material = mat
        return mat
    return default

def ask_density(element_label, default=7850.0):
    global apply_to_all_dens, global_density
    if apply_to_all_dens:
        return global_density
    dlg = QtWidgets.QDialog()
    dlg.setWindowTitle("Gęstość stali")
    layout = QtWidgets.QVBoxLayout(dlg)

    lbl_elem = QtWidgets.QLabel(f"Element: {element_label}")
    lbl_elem.setStyleSheet("font-weight: bold;")
    layout.addWidget(lbl_elem)

    form_layout = QtWidgets.QHBoxLayout()
    label = QtWidgets.QLabel("Gęstość stali:")
    textbox = QtWidgets.QLineEdit()
    textbox.setText(str(default))
    unit = QtWidgets.QLabel("kg/m³")
    form_layout.addWidget(label)
    form_layout.addWidget(textbox)
    form_layout.addWidget(unit)
    layout.addLayout(form_layout)

    checkbox = QtWidgets.QCheckBox("Zastosuj do wszystkich pozycji")
    layout.addWidget(checkbox)

    button_box = QtWidgets.QDialogButtonBox(QtWidgets.QDialogButtonBox.Ok)
    layout.addWidget(button_box)
    button_box.accepted.connect(dlg.accept)

    if dlg.exec_() == QtWidgets.QDialog.Accepted:
        try:
            dens = float(textbox.text().strip())
        except Exception:
            dens = default
        if checkbox.isChecked():
            apply_to_all_dens = True
            global_density = dens
        return dens
    return default

# --- Zbieranie danych dla elementów pojedynczych ---

single_data = {}

# 1) Elementy pojedyncze w modelu centralnym
for o in doc.Objects:
    m = re_single.match(o.Label or "")
    if not m:
        continue
    pref = m.group(1)
    sd = single_data.setdefault(pref, {"ilosc":0, "dlugosc":0.0, "szer":0.0, "wys":0.0, "nazwa":"?"})
    sd["ilosc"] += 1

# 2) Elementy pojedyncze wewnątrz elementów wysyłkowych
for o in doc.Objects:
    m = re_ew.match(o.Label or "")
    if not m:
        continue
    pref_ew = m.group(1)
    fcstd_path = os.path.join(MAIN_DIR, f"{pref_ew}.FCStd")
    if not os.path.isfile(fcstd_path):
        continue
    try:
        td = App.openDocument(fcstd_path)
    except Exception:
        continue
    try:
        for p in td.Objects:
            m2 = re_single.match(p.Label or "")
            if not m2:
                continue
            pref_single = m2.group(1)
            sd = single_data.setdefault(pref_single, {"ilosc":0, "dlugosc":0.0, "szer":0.0, "wys":0.0, "nazwa":"?"})
            sd["ilosc"] += 1
    finally:
        try:
            App.closeDocument(td.Name)
        except Exception:
            pass

# 3) Uzupełnienie danych z plików SINGLE
for pref, data in single_data.items():
    fcstd_path = os.path.join(SINGLE_DIR, f"{pref}.FCStd")
    if not os.path.isfile(fcstd_path):
        continue
    try:
        td = App.openDocument(fcstd_path)
    except Exception:
        continue
    try:
        for o in td.Objects:
            if hasattr(o, "Shape") and o.Shape and not o.Shape.isNull():
                L, W, H = get_dims_from_bbox(o)
                data["dlugosc"] = max(data["dlugosc"], L)
                data["szer"] = max(data["szer"], W)
                data["wys"] = max(data["wys"], H)
                if data["nazwa"] == "?":
                    # jeśli mamy obiekt Frame, spróbujmy zajrzeć do jego dzieci
                    if "frame" in (o.Label or "").lower() or o.Name.lower().startswith("frame"):
                        for c in getattr(o, "OutList", []):
                            if c.Label and c.Label.lower() != "line":
                                data["nazwa"] = c.Label
                                break
                        else:
                            data["nazwa"] = o.Label or "?"
                    else:
                        # ignorujemy obiekty o nazwie "Line"
                        if o.Label and o.Label.lower() != "line":
                            data["nazwa"] = o.Label
    finally:
        try:
            App.closeDocument(td.Name)
        except Exception:
            pass

# --- Arkusz ---

if "BOM_EP" in doc.Objects:
    sheet = doc.getObject("BOM_EP")
    try:
        sheet.clearAll()
    except Exception:
        pass
else:
    sheet = doc.addObject("Spreadsheet::Sheet","BOM_EP")

sheet.set("A1","LIST OF SINGLE ELEMENTS")
sheet.set("A2","ITEM")
sheet.set("B2","NAME")
sheet.set("C2","QUANTITY (pcs.)")
sheet.set("D2","LENGHT [mm]")
sheet.set("E2","WIDTH [mm]")
sheet.set("F2","HEIGHT [mm]")
sheet.set("G2","MATERIAL")
sheet.set("H2","WEIGHT OF 1 pcs. [kg]")
sheet.set("I2","WEIGHT [kg]")

row = 3
total_weight = 0.0

for pref, data in sorted(single_data.items()):
    # przekazujemy label elementu do dialogów (tylko OK)
    material = ask_material(pref)
    density = ask_density(pref)
    vol_m3 = (data["dlugosc"] * data["szer"] * data["wys"]) / 1e9
    waga_elem = vol_m3 * density
    waga_total = waga_elem * data["ilosc"]

    sheet.set(f"A{row}", pref)
    sheet.set(f"B{row}", data["nazwa"])
    sheet.set(f"C{row}", str(data["ilosc"]))
    sheet.set(f"D{row}", f"{data['dlugosc']:.2f}")
    sheet.set(f"E{row}", f"{data['szer']:.2f}")
    sheet.set(f"F{row}", f"{data['wys']:.2f}")
    sheet.set(f"G{row}", material)
    sheet.set(f"H{row}", f"{waga_elem:.3f}")
    sheet.set(f"I{row}", f"{waga_total:.3f}")

    total_weight += waga_total
    row += 1

# Podsumowanie
sheet.set(f"H{row}", "TOTAL WEIGHT [kg]")
sheet.set(f"I{row}", f"{total_weight:.3f}")

try:
    doc.recompute()
except Exception:
    pass

App.Console.PrintMessage("Arkusz BOM_EP utworzony z nagłówkiem i podsumowaniem.\n")

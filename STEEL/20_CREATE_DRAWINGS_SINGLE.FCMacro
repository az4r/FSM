# 20_CREATE_DRAWINGS_SINGLE.FCMacro
# Minimalna zmiana: rozdzielony maksymalny rozmiar elementu na osie X i Y:
# - max_element_x_mm kontroluje szerokość siatki (offset_x),
# - max_element_y_mm kontroluje wysokość siatki (offset_y).
# Reszta makra pozostaje bez zmian.

import FreeCAD as App, os, re, json
import a2p_importpart
import TechDraw
from PySide2 import QtWidgets

# Stałe szerokości kolumn (synchronizowane z 19_CREATE_DRAWINGS_MAIN)
DEFAULT_COLUMN_WIDTH = 125   # szerokość kolumny w arkuszu (px)
POSITION_COLUMN_WIDTH = 33   # szerokość kolumny używana do pozycjonowania tabeli (mm)

def log(msg):
    App.Console.PrintMessage(str(msg) + "\n")

def apply_fixed_column_widths_to_sheet(sheet, width_px, cell_start="A1", cell_end="I999"):
    try:
        width_px = int(width_px)
    except Exception:
        width_px = 100
    try:
        start_col = re.match(r"([A-Z]+)", cell_start).group(1)
        end_col   = re.match(r"([A-Z]+)", cell_end).group(1)
    except Exception:
        start_col, end_col = "A", "I"
    for c_ord in range(ord(start_col), ord(end_col) + 1):
        col_letter = chr(c_ord)
        try:
            sheet.setColumnWidth(col_letter, width_px)
        except Exception:
            try:
                if hasattr(sheet, "setColumnWidthInPixels"):
                    sheet.setColumnWidthInPixels(col_letter, width_px)
            except Exception:
                pass

def get_project_dir():
    if App.ActiveDocument and getattr(App.ActiveDocument, "FileName", ""):
        return os.path.dirname(App.ActiveDocument.FileName)
    raise Exception("Zapisz i otwórz dokument projektu zanim uruchomisz makro.")

def list_templates():
    tpl_dir = os.path.join(App.getResourceDir(), "Mod", "TechDraw", "Templates")
    if not os.path.isdir(tpl_dir):
        log(f"!!! Nie znaleziono katalogu Templates: {tpl_dir}")
        return []
    return [f for f in os.listdir(tpl_dir) if f.lower().endswith("svg")]

def select_template_and_scale():
    files = list_templates()
    if not files:
        return None, None
    dlg = QtWidgets.QDialog()
    dlg.setWindowTitle("Ustawienia rysunku TechDraw")
    layout = QtWidgets.QVBoxLayout(dlg)
    scale_layout = QtWidgets.QHBoxLayout()
    scale_label = QtWidgets.QLabel("Skala:")
    scale_combo = QtWidgets.QComboBox()
    scale_combo.addItems(["1:1", "1:10", "1:50", "1:100", "1:200"])
    scale_layout.addWidget(scale_label)
    scale_layout.addWidget(scale_combo)
    layout.addLayout(scale_layout)
    tpl_label = QtWidgets.QLabel("Szablon:")
    tpl_combo = QtWidgets.QComboBox()
    tpl_combo.addItems(files)
    layout.addWidget(tpl_label)
    layout.addWidget(tpl_combo)
    btn_ok = QtWidgets.QPushButton("OK")
    layout.addWidget(btn_ok)
    btn_ok.clicked.connect(dlg.accept)
    dlg.exec_()
    return tpl_combo.currentText(), scale_combo.currentText()

apply_to_all_mat = False
global_material = "S355J2"
apply_to_all_dens = False
global_density = 7850.0

def ask_material(element_label, default="S355J2"):
    global apply_to_all_mat, global_material
    if apply_to_all_mat:
        return global_material
    dlg = QtWidgets.QDialog()
    dlg.setWindowTitle("Gatunek stali")
    layout = QtWidgets.QVBoxLayout(dlg)
    lbl_elem = QtWidgets.QLabel(f"Element: {element_label}")
    lbl_elem.setStyleSheet("font-weight: bold;")
    layout.addWidget(lbl_elem)
    form_layout = QtWidgets.QHBoxLayout()
    label = QtWidgets.QLabel("Gatunek stali:")
    textbox = QtWidgets.QLineEdit()
    textbox.setText(default)
    form_layout.addWidget(label)
    form_layout.addWidget(textbox)
    layout.addLayout(form_layout)
    cb = QtWidgets.QCheckBox("Zastosuj do wszystkich pozycji")
    layout.addWidget(cb)
    box = QtWidgets.QDialogButtonBox(QtWidgets.QDialogButtonBox.Ok)
    layout.addWidget(box)
    box.accepted.connect(dlg.accept)
    if dlg.exec_() == QtWidgets.QDialog.Accepted:
        m = textbox.text().strip() or default
        if cb.isChecked():
            apply_to_all_mat = True
            global_material = m
        return m
    return default

def ask_density(element_label, default=7850.0):
    global apply_to_all_dens, global_density
    if apply_to_all_dens:
        return global_density
    dlg = QtWidgets.QDialog()
    dlg.setWindowTitle("Gęstość stali")
    layout = QtWidgets.QVBoxLayout(dlg)
    lbl_elem = QtWidgets.QLabel(f"Element: {element_label}")
    lbl_elem.setStyleSheet("font-weight: bold;")
    layout.addWidget(lbl_elem)
    form_layout = QtWidgets.QHBoxLayout()
    label = QtWidgets.QLabel("Gęstość stali:")
    textbox = QtWidgets.QLineEdit()
    textbox.setText(str(default))
    unit = QtWidgets.QLabel("kg/m³")
    form_layout.addWidget(label)
    form_layout.addWidget(textbox)
    form_layout.addWidget(unit)
    layout.addLayout(form_layout)
    cb = QtWidgets.QCheckBox("Zastosuj do wszystkich pozycji")
    layout.addWidget(cb)
    box = QtWidgets.QDialogButtonBox(QtWidgets.QDialogButtonBox.Ok)
    layout.addWidget(box)
    box.accepted.connect(dlg.accept)
    if dlg.exec_() == QtWidgets.QDialog.Accepted:
        try:
            d = float(textbox.text().strip())
        except Exception:
            d = default
        if cb.isChecked():
            apply_to_all_dens = True
            global_density = d
        return d
    return default

def _get_dims_from_bbox(obj):
    try:
        if not hasattr(obj, "Shape") or obj.Shape is None or obj.Shape.isNull():
            return (0.0,0.0,0.0)
        bb = obj.Shape.BoundBox
        dims = [bb.XLength, bb.YLength, bb.ZLength]
        dims.sort(reverse=True)
        return dims[0], dims[1], dims[2]
    except Exception:
        return (0.0,0.0,0.0)

def collect_single_data_from_main(main_doc, single_dir, main_dir):
    re_ew     = re.compile(r"^(\d{3})_")
    re_single = re.compile(r"^(\d{4})_")
    single_data = {}
    for o in main_doc.Objects:
        m = re_single.match(o.Label or "")
        if not m: continue
        pref = m.group(1)
        sd = single_data.setdefault(pref, {"ilosc":0,"dlugosc":0.0,"szer":0.0,"wys":0.0,"nazwa":"?","ews": set()})
        sd["ilosc"] += 1
    for o in main_doc.Objects:
        m = re_ew.match(o.Label or "")
        if not m: continue
        pref_ew = m.group(1)
        fcstd_path = os.path.join(main_dir, f"{pref_ew}.FCStd")
        if not os.path.isfile(fcstd_path): continue
        try:
            td = App.openDocument(fcstd_path)
        except Exception:
            continue
        try:
            for p in td.Objects:
                m2 = re_single.match(p.Label or "")
                if not m2: continue
                pref_single = m2.group(1)
                sd = single_data.setdefault(pref_single, {"ilosc":0,"dlugosc":0.0,"szer":0.0,"wys":0.0,"nazwa":"?","ews": set()})
                sd["ilosc"] += 1
                sd["ews"].add(pref_ew)
        finally:
            try: App.closeDocument(td.Name)
            except Exception: pass
    for pref, data in single_data.items():
        fcstd_path = os.path.join(single_dir, f"{pref}.FCStd")
        if not os.path.isfile(fcstd_path): continue
        try:
            td = App.openDocument(fcstd_path)
        except Exception:
            continue
        try:
            for o in td.Objects:
                if hasattr(o, "Shape") and o.Shape and not o.Shape.isNull():
                    L,W,H = _get_dims_from_bbox(o)
                    data["dlugosc"] = max(data["dlugosc"], L)
                    data["szer"]    = max(data["szer"], W)
                    data["wys"]     = max(data["wys"], H)
                    if data["nazwa"] == "?":
                        if o.Label and o.Label.lower() != "line":
                            data["nazwa"] = o.Label
        finally:
            try: App.closeDocument(td.Name)
            except Exception: pass
    for k,v in single_data.items():
        if isinstance(v.get("ews"), set):
            v["ews"] = sorted(list(v["ews"]))
    return single_data

def create_single_assembly_and_open(docname, single_dir, draw_dir):
    doc = App.newDocument(docname)
    App.setActiveDocument(doc.Name)
    App.ActiveDocument = doc
    doc_path = os.path.join(draw_dir, f"{docname}.FCStd")
    try:
        doc.saveAs(doc_path)
    except Exception:
        pass
    files = []
    if os.path.isdir(single_dir):
        files = [f for f in os.listdir(single_dir) if f.lower().endswith("fcstd")]
    if not files:
        log(f"!!! Brak plików w katalogu: {single_dir}")
        return doc
    offset = 0
    for f in files:
        filepath = os.path.join(single_dir, f)
        try:
            root = a2p_importpart.importPartFromFile(doc, filepath)
            if root:
                root.Placement.Base.x = offset
                log(f">>> Zaimportowano {f} na X={offset}")
                offset += 30000
        except Exception as e:
            log(f"!!! Błąd importu {f}: {e}")
    try:
        doc.recompute()
        doc.save()
    except Exception:
        pass
    log(f">>> Utworzono {docname} z {len(files)} plików")
    return doc

def choose_main_document(draw_dir, main_dir):
    ad = App.ActiveDocument
    re_ew = re.compile(r"^(\d{3})_")
    re_single = re.compile(r"^(\d{4})_")
    def looks_like_main(doc):
        if not doc: return False
        try:
            fn = getattr(doc, "FileName", "") or ""
            if fn:
                if os.path.sep + "MAIN" + os.path.sep in fn.upper() or "MAIN" in os.path.basename(fn).upper():
                    return True
            for o in doc.Objects:
                if re_ew.match(o.Label or "") or re_single.match(o.Label or ""):
                    return True
        except Exception:
            return False
        return False
    if looks_like_main(ad):
        log(f"[INFO] Używam aktywnego dokumentu jako MAIN: {ad.Name}")
        return ad
    candidate = os.path.join(draw_dir, "MAIN_ASSEMBLY.FCStd")
    if os.path.isfile(candidate):
        try:
            md = App.openDocument(candidate)
            log(f"[INFO] Otwieram MAIN_ASSEMBLY z DRAWINGS: {candidate}")
            return md
        except Exception:
            pass
    candidate2 = os.path.join(main_dir, "MAIN_ASSEMBLY.FCStd")
    if os.path.isfile(candidate2):
        try:
            md = App.openDocument(candidate2)
            log(f"[INFO] Otwieram MAIN_ASSEMBLY z MAIN: {candidate2}")
            return md
        except Exception:
            pass
    if os.path.isdir(main_dir):
        for fname in os.listdir(main_dir):
            if fname.lower().endswith("fcstd"):
                fp = os.path.join(main_dir, fname)
                try:
                    md = App.openDocument(fp)
                    log(f"[INFO] Otwieram pierwszy .FCStd z MAIN_DIR: {fp}")
                    return md
                except Exception:
                    continue
    return None

def set_view_position_via_viewobject(view, x, y):
    try:
        vo = view.ViewObject
        if hasattr(vo, "X") and hasattr(vo, "Y"):
            vo.X = float(x)
            vo.Y = float(y)
            try:
                vo.update()
            except Exception:
                pass
            return True
    except Exception:
        pass
    try:
        view.X = float(x)
        view.Y = float(y)
        return True
    except Exception:
        try:
            view.X = x
            view.Y = y
            return True
        except Exception:
            return False

# --- Główna funkcja tworząca stronę, widoki i per-strona tabelę + etykiety ---
def create_single_overview_grid_centered_with_table(main_doc, single_doc, template_name, scale_str, single_data):
    tpl_dir = os.path.join(App.getResourceDir(), "Mod", "TechDraw", "Templates")
    tpl_path = os.path.join(tpl_dir, template_name)
    if not os.path.isfile(tpl_path):
        log(f"!!! Nie znaleziono szablonu: {tpl_path}")
        return
    try:
        num, den = scale_str.split(":")
        scale_val = float(num) / float(den)
    except Exception:
        scale_val = 1.0

    # --- ZMIANA: niezależne max rozmiary w osiach X/Y ---
    # Domyślne wartości - dostosuj według potrzeb projektu
    max_element_x_mm = 3000.0   # maksymalna długość elementu w poziomie (mm)
    max_element_y_mm = 6000.0   # maksymalna wysokość elementu w pionie (mm)

    # Skalowane rozmiary widoku w mm
    view_size_x = max_element_x_mm * scale_val
    view_size_y = max_element_y_mm * scale_val

    # marginesy i odstępy (mm)
    margin = 30.0
    gap = 10.0

    offset_x = view_size_x + gap
    offset_y = view_size_y + gap

    template_obj = single_doc.addObject('TechDraw::DrawSVGTemplate', "Template_SingleOverview")
    template_obj.Template = tpl_path
    page = single_doc.addObject('TechDraw::DrawPage', "Page_SingleOverview")
    page.Template = template_obj

    try:
        pw = float(template_obj.Width)
        ph = float(template_obj.Height)
    except Exception:
        pw = 210.0; ph = 297.0

    usable_w = pw - 2*margin
    usable_h = ph - 2*margin
    cols_fit = max(1, int(usable_w // offset_x))
    rows_fit = max(1, int(usable_h // offset_y))
    log(f"[GRID] page W={pw} H={ph} scale={scale_val} view_size_x={view_size_x:.2f} view_size_y={view_size_y:.2f} cols_fit={cols_fit} rows_fit={rows_fit}")

    left_start = margin + view_size_x/2.0
    top_start = ph - margin - view_size_y/2.0

    items = sorted(single_data.keys())
    page_index = 0
    cell_index = 0

    def new_page(doc, tpl_path, page_index):
        t = doc.addObject('TechDraw::DrawSVGTemplate', f"Template_SingleOverview_{page_index}")
        t.Template = tpl_path
        p = doc.addObject('TechDraw::DrawPage', f"Page_SingleOverview_{page_index}")
        p.Template = t
        return t, p

    current_template = template_obj
    current_page = page

    created_views = []
    created_prefs = []
    page_to_prefs = {}

    for pref in items:
        src = None
        for o in single_doc.Objects:
            try:
                if (o.Label or "").startswith(pref):
                    src = o; break
            except Exception:
                continue
        if not src:
            log(f"[WARN] Nie znaleziono obiektu SINGLE dla {pref} w SINGLE_ASSEMBLY; pomijam")
            continue

        page_slot = cell_index // (cols_fit * rows_fit)
        index_in_page = cell_index % (cols_fit * rows_fit)
        col = index_in_page // rows_fit
        row = index_in_page % rows_fit

        if page_slot > page_index:
            page_index = page_slot
            current_template, current_page = new_page(single_doc, tpl_path, page_index)

        cx = left_start + col * offset_x
        cy = top_start - row * offset_y

        try:
            view = single_doc.addObject('TechDraw::DrawViewPart', f"View_{pref}")
            view.Source = [src]
            view.Direction = (0,1,0)
            view.ScaleType = "Custom"
            view.Scale = scale_val
            current_page.addView(view)
            try:
                if hasattr(view, "ViewObject") and hasattr(view.ViewObject, "X"):
                    view.ViewObject.X = float(cx)
                    view.ViewObject.Y = float(cy)
                else:
                    view.X = float(cx)
                    view.Y = float(cy)
            except Exception:
                try:
                    set_view_position_via_viewobject(view, cx, cy)
                except Exception:
                    pass
            try: view.recompute()
            except Exception: pass

            created_views.append(view)
            created_prefs.append(pref)
            page_to_prefs.setdefault(current_page, []).append(pref)

            log(f">>> View_{pref} page={page_index} col={col} row={row} cx={cx:.2f} cy={cy:.2f}")
        except Exception as e:
            log(f"[WARN] Nie udało się utworzyć widoku dla {pref}: {e}")

        cell_index += 1

    try:
        single_doc.recompute()
        single_doc.save()
    except Exception:
        pass

    log(f">>> Utworzono {len(created_views)} widoków na {page_index+1} stronach.")

    # Tabele per-strona
    try:
        for page_obj, prefs_on_page in page_to_prefs.items():
            try:
                sheet_name = f"BOM_{page_obj.Name}"
                sheet = single_doc.addObject("Spreadsheet::Sheet", sheet_name)

                sheet.set("A1", "LIST OF SINGLE ELEMENTS")
                sheet.set("A2","ITEM")
                sheet.set("B2","NAME")
                sheet.set("C2","QUANTITY (pcs.)")
                sheet.set("D2","LENGHT [mm]")
                sheet.set("E2","WIDTH [mm]")
                sheet.set("F2","HEIGHT [mm]")
                sheet.set("G2","MATERIAL")
                sheet.set("H2","WEIGHT OF 1 pcs. [kg]")
                sheet.set("I2","WEIGHT [kg]")

                try:
                    sheet.mergeCells("A1:I1")
                except Exception:
                    try:
                        if hasattr(sheet, "mergeRange"):
                            sheet.mergeRange("A1","I1")
                        elif hasattr(sheet, "setMergedCells"):
                            sheet.setMergedCells(["A1:I1"])
                    except Exception:
                        pass

                row = 3
                total_weight = 0.0
                for pref in sorted(prefs_on_page):
                    data = single_data.get(pref, {})
                    material = ask_material(pref, "S355J2")
                    density = ask_density(pref, 7850.0)
                    vol_m3 = (data.get("dlugosc",0.0) * data.get("szer",0.0) * data.get("wys",0.0)) / 1e9
                    waga_elem = vol_m3 * density
                    waga_total = waga_elem * data.get("ilosc",0)

                    sheet.set(f"A{row}", pref)
                    sheet.set(f"B{row}", data.get("nazwa","?"))
                    sheet.set(f"C{row}", str(data.get("ilosc",0)))
                    sheet.set(f"D{row}", f"{data.get('dlugosc',0.0):.2f}")
                    sheet.set(f"E{row}", f"{data.get('szer',0.0):.2f}")
                    sheet.set(f"F{row}", f"{data.get('wys',0.0):.2f}")
                    sheet.set(f"G{row}", material)
                    sheet.set(f"H{row}", f"{waga_elem:.3f}")
                    sheet.set(f"I{row}", f"{waga_total:.3f}")

                    total_weight += waga_total
                    row += 1

                summary_row = row if row > 3 else 3
                sheet.set(f"H{summary_row}", "TOTAL WEIGHT [kg]")
                sheet.set(f"I{summary_row}", f"{total_weight:.3f}")

                try: single_doc.recompute()
                except Exception: pass

                cell_start = "A1"
                cell_end = f"I{summary_row}"

                try:
                    apply_fixed_column_widths_to_sheet(sheet, DEFAULT_COLUMN_WIDTH, cell_start, cell_end)
                    try: single_doc.recompute()
                    except Exception: pass
                except Exception:
                    pass

                table_view = single_doc.addObject("TechDraw::DrawViewSpreadsheet", f"Table_{page_obj.Name}")
                table_view.Source = sheet
                try:
                    table_view.CellStart = cell_start
                    table_view.CellEnd = cell_end
                except Exception:
                    try:
                        vo = table_view.ViewObject
                        if hasattr(vo, "CellStart"): vo.CellStart = cell_start
                        if hasattr(vo, "CellEnd"): vo.CellEnd = cell_end
                    except Exception:
                        pass

                try:
                    vo = table_view.ViewObject
                    if hasattr(vo, "FontSize"): vo.FontSize = 10
                    if hasattr(vo, "RowHeight"): vo.RowHeight = 6
                    vo.Visibility = True
                except Exception:
                    pass

                page_obj.addView(table_view)

                filled_rows = summary_row
                filled_cols = 9  # A..I
                row_height_mm = 6.0
                col_width_mm = POSITION_COLUMN_WIDTH
                table_h_mm = filled_rows * row_height_mm
                table_w_mm = filled_cols * col_width_mm

                left_margin = 30.0
                bottom_margin = 30.0
                safe_offset = 2.0
                center_x = left_margin + safe_offset + (table_w_mm / 2.0)
                center_y = bottom_margin + safe_offset + (table_h_mm / 2.0)

                try:
                    vo = table_view.ViewObject
                    if hasattr(vo, "X"): vo.X = float(center_x)
                    if hasattr(vo, "Y"): vo.Y = float(center_y)
                    try: vo.update()
                    except Exception: pass
                except Exception:
                    pass

                try:
                    table_view.X = float(center_x)
                    table_view.Y = float(center_y)
                except Exception:
                    pass

                try:
                    table_view.Width = table_w_mm
                    table_view.Height = table_h_mm
                except Exception:
                    pass

                try: table_view.recompute()
                except Exception: pass
                try: single_doc.recompute()
                except Exception: pass

                log(f"[TABLE] {sheet.Name} zakres={cell_start}:{cell_end} size={table_w_mm:.2f}x{table_h_mm:.2f}")
            except Exception as e:
                log(f"[TABLE] Błąd przy tworzeniu tabeli dla strony {getattr(page_obj,'Name',str(page_obj))}: {e}")
    except Exception as e:
        log(f"[TABLE] Błąd globalny: {e}")

    # Etykiety per widok: na właściwej stronie; grupa wyśrodkowana (Info po lewej, Number po prawej)
    try:
        for v in created_views:
            try:
                if not hasattr(v, "TypeId"): continue
                if not str(getattr(v, "TypeId", "")).startswith("TechDraw::DrawViewPart"): continue

                try:
                    page_for_view = next((p for p in v.InList if hasattr(p, "TypeId") and str(p.TypeId).startswith("TechDraw::DrawPage")), None)
                except Exception:
                    page_for_view = None
                if page_for_view is None:
                    page_for_view = current_page

                m = re.search(r"(\d{3,4})", v.Name)
                if m:
                    pref = m.group(1)
                else:
                    pref = getattr(v, "Label", None)
                    if not pref:
                        continue

                data = single_data.get(pref, {})
                qty = int(float(data.get("ilosc", 0))) if data.get("ilosc", 0) else 0
                qty_text = f"{qty}x"
                num_text = str(pref)
                scale_text = scale_str if 'scale_str' in locals() else ""

                try:
                    vx = float(getattr(v, "X", getattr(getattr(v, "ViewObject", None), "X", 0.0)))
                    vy = float(getattr(v, "Y", getattr(getattr(v, "ViewObject", None), "Y", 0.0)))
                except Exception:
                    vx = float(getattr(v, "X", 0.0))
                    vy = float(getattr(v, "Y", 0.0))

                try:
                    # wysokość widoku - używamy view_size_y (skrocony widok w osi Y)
                    vheight = float(getattr(v, "Height", getattr(getattr(v, "ViewObject", None), "Height", view_size_y)))
                except Exception:
                    vheight = view_size_y

                label_center_y = vy + (vheight / 2.0) + 6.0

                # INFO po lewej
                anno_info = single_doc.addObject('TechDraw::DrawRichAnno', f"Anno_Info_{pref}")
                try:
                    page_for_view.addView(anno_info)
                except Exception:
                    pass
                anno_info.AnnoText = """<!DOCTYPE HTML PUBLIC "-//W3C//DTD HTML 4.0//EN" "http://www.w3.org/TR/REC-html40/strict.dtd">
<html>
<head><meta name="qrichtext" content="1" /></head>
<body style="font-family:'Arial'; font-size:7pt; font-weight:normal; text-align:left;">
<p style="margin:0px;">%s</p>
<p style="margin:0px;">%s</p>
</body>
</html>""" % (qty_text, scale_text)
                anno_info.ShowFrame = False

                # NUMBER po prawej
                anno_num = single_doc.addObject('TechDraw::DrawRichAnno', f"Anno_Number_{pref}")
                try:
                    page_for_view.addView(anno_num)
                except Exception:
                    pass
                anno_num.AnnoText = """<!DOCTYPE HTML PUBLIC "-//W3C//DTD HTML 4.0//EN" "http://www.w3.org/TR/REC-html40/strict.dtd">
<html>
<head><meta name="qrichtext" content="1" /></head>
<body style="font-family:'Arial'; font-size:10pt; font-weight:normal; text-align:left;">
<p style="margin:0px; text-align:left;">%s</p>
</body>
</html>""" % (num_text)
                anno_num.ShowFrame = True

                # Wyśrodkowanie grupy (Info po lewej, Number po prawej)
                try:
                    info_w = 25.0
                    num_w  = 40.0
                    gap    = 6.0
                    group_width = info_w + gap + num_w
                    group_left = vx - group_width/2.0

                    anno_info.X = float(group_left + info_w/2.0)
                    anno_info.Y = float(label_center_y)
                    anno_num.X  = float(group_left + info_w + gap + num_w/2.0)
                    anno_num.Y  = float(label_center_y)
                except Exception:
                    try:
                        anno_num.X = float(vx)
                        anno_num.Y = float(label_center_y)
                        anno_info.X = float(vx - 25.0)
                        anno_info.Y = float(label_center_y)
                    except Exception:
                        pass

                try:
                    single_doc.recompute()
                except Exception:
                    pass

            except Exception as e:
                log(f"[ANNOT] Błąd podczas dodawania adnotacji dla widoku {getattr(v,'Name',str(v))}: {e}")
    except Exception as e:
        log(f"[ANNOT] Błąd ogólny: {e}")

# ENTRYPOINT
try:
    proj_dir = get_project_dir()
    single_dir = os.path.join(proj_dir, "SINGLE")
    main_dir   = os.path.join(proj_dir, "MAIN")
    draw_dir   = os.path.join(proj_dir, "DRAWINGS")
    os.makedirs(draw_dir, exist_ok=True)

    log("=== START CREATE_DRAWINGS_SINGLE ===")

    main_doc = choose_main_document(draw_dir, main_dir)
    if not main_doc:
        raise Exception("Nie udało się odnaleźć lub otworzyć dokumentu MAIN. Upewnij się, że aktywny dokument to MAIN lub że istnieje MAIN_ASSEMBLY.FCStd lub inne .FCStd w katalogu MAIN.")

    single_data = collect_single_data_from_main(main_doc, single_dir, main_dir)
    if not single_data:
        log("Brak wykrytych elementów pojedynczych w MAIN. Kończę.")
        raise SystemExit

    single_doc = create_single_assembly_and_open("SINGLE_ASSEMBLY", single_dir, draw_dir)

    tpl, scale = select_template_and_scale()
    if not tpl or not scale:
        log("Nie wybrano szablonu lub skali. Anuluję.")
        raise SystemExit

    create_single_overview_grid_centered_with_table(main_doc, single_doc, tpl, scale, single_data)

    log("=== KONIEC CREATE_DRAWINGS_SINGLE ===")

except Exception as e:
    log(f"!!! FAIL: {e}")
